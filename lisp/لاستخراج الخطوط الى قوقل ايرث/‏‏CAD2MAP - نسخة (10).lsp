;;; حقوق المصدر: محفوظة لأصحابها كما وردت في الملف الأصلي؛ لا يُدّعى نقل ملكيتها.
;;; المراجعة: نسخة مجمّعة مع فحص ساكن وتحسينات موضحة في دليل الأدوات.
;;; اختصار التشغيل: CE
;;; الملف الأصلي: ‏‏CAD2MAP - نسخة (10).lsp
;;; =========================================================================
;;;  Tool: CADEARTH PRO - AutoCAD to Web GIS & KML Exporter
;;;  Shortcuts: CE, CADEARTH, CAD2MAP, CAD2EARTH
;;;  Publisher: AL3MER / Technical Office
;;;  Version: 3.1 (Chunked Stream Output - Fixes "string too long on input")
;;; =========================================================================

(vl-load-com)

;; دالة الظل الرياضية
(defun _tan (ang) (/ (sin ang) (cos ang)))

;; دالة تجزئة نصية لتوليد ألوان ثابتة للطبقات
(defun Str-Hash (s / i sum)
  (setq sum 0 i 0)
  (while (< i (strlen s))
    (setq sum (+ sum (ascii (substr s (1+ i) 1))))
    (setq i (1+ i))
  )
  sum
)

;; لون KML ثابت حسب اسم الطبقة
(defun Layer-Color-KML (lyr / palette h)
  (setq palette '("ff3b82f6" "ff10b981" "ffef4444" "fff59e0b"
                  "ff8b5cf6" "ffec4899" "ff14b8a6" "ffef8354"))
  (setq h (rem (Str-Hash (if lyr lyr "0")) (length palette)))
  (nth h palette)
)

;; فحص إمكانية الكتابة في المجلد لتفادي أخطاء الصلاحيات
(defun Is-Writable-Dir (dir / testFile f res)
  (setq res nil)
  (if (and dir (/= dir ""))
    (progn
      (setq testFile (strcat dir "chk_perm_" (rtos (getvar "CDATE") 2 6) ".tmp"))
      (setq f (open testFile "w"))
      (if f
        (progn
          (close f)
          (vl-file-delete testFile)
          (setq res T)
        )
      )
    )
  )
  res
)

;; تحويل إحداثيات UTM إلى Lat/Lon WGS84 بدقة هندسية عالية
(defun UTM->WGS84 (east north zone south / a f e2 e e1 rad2deg deg2rad M mu J1 J2 J3 J4 phi1 C1 T1 N1 R1 D lat lon)
  (setq a 6378137.0
        f (/ 1.0 298.257223563)
        e2 (* f (- 2.0 f))
        e (sqrt e2)
        e1 (/ (- 1.0 (sqrt (- 1.0 e2))) (+ 1.0 (sqrt (- 1.0 e2))))
        rad2deg (/ 180.0 pi)
        deg2rad (/ pi 180.0))

  (setq east (- (float east) 500000.0))
  (if (and south (or (eq south T) (= south "1") (= south 1)))
    (setq north (- (float north) 10000000.0))
    (setq north (float north))
  )
  (setq M (/ north 0.9996))
  (setq mu (/ M (* a (- 1.0 (/ e2 4.0) (/ (* 3.0 e2 e2) 64.0) (/ (* 5.0 (expt e2 3)) 256.0)))))

  (setq J1 (- (/ (* 3.0 e1) 2.0) (/ (* 27.0 (expt e1 3)) 32.0)))
  (setq J2 (- (/ (* 21.0 (* e1 e1)) 16.0) (/ (* 55.0 (expt e1 4)) 32.0)))
  (setq J3 (/ (* 151.0 (expt e1 3)) 96.0))
  (setq J4 (/ (* 1097.0 (expt e1 4)) 512.0))

  (setq phi1 (+ mu (* J1 (sin (* 2.0 mu))) (* J2 (sin (* 4.0 mu))) (* J3 (sin (* 6.0 mu))) (* J4 (sin (* 8.0 mu)))))

  (setq C1 (* (/ e2 (- 1.0 e2)) (* (cos phi1) (cos phi1))))
  (setq T1 (* (_tan phi1) (_tan phi1)))
  (setq N1 (/ a (sqrt (- 1.0 (* e2 (sin phi1) (sin phi1))))))
  (setq R1 (/ (* a (- 1.0 e2)) (expt (- 1.0 (* e2 (sin phi1) (sin phi1))) 1.5)))
  (setq D (/ east (* N1 0.9996)))

  (setq lat (- phi1
               (* (/ (* N1 (_tan phi1)) R1)
                  (- (/ (* D D) 2.0)
                     (/ (* (+ 5.0 (* 3.0 T1) (* 10.0 C1) (* -4.0 C1 C1)) (expt D 4)) 24.0)
                     (/ (* (+ 61.0 (* 90.0 T1) (* 298.0 C1) (* 45.0 T1 T1)) (expt D 6)) 720.0)))))

  (setq lon (+ (/ (- D
                     (/ (* (+ 1.0 (* 2.0 T1) C1) (expt D 3)) 6.0)
                     (/ (* (+ 5.0 (* 28.0 T1) (* 24.0 T1 T1)) (expt D 5)) 120.0))
                  (cos phi1))
               (* (- (* (float zone) 6.0) 183.0) deg2rad)))

  (list (* lon rad2deg) (* lat rad2deg))
)

;; حفظ ملفات KML / GeoJSON بترميز UTF-8
(defun Write-UTF8 (filePath content / stream f success)
  (setq success nil)
  (if (not (vl-catch-all-error-p
             (vl-catch-all-apply
               '(lambda ()
                  (setq stream (vlax-create-object "ADODB.Stream"))
                  (vlax-put-property stream 'Type 2)
                  (vlax-put-property stream 'Charset "utf-8")
                  (vlax-invoke-method stream 'Open)
                  (vlax-invoke-method stream 'WriteText content)
                  (vlax-invoke-method stream 'SaveToFile filePath 2)
                  (vlax-invoke-method stream 'Close)
                  (vlax-release-object stream)
                  (setq success T)
                ))))
    (setq success T)
  )
  (if (not success)
    (if (setq f (open filePath "w"))
      (progn
        (write-line content f)
        (close f)
        (setq success T)
      )
    )
  )
  success
)

;; تحويل القوس ARC إلى سلسلة نقاط
(defun Tessellate-Arc (ent / edata center radius startAng endAng elev seg pts ang i)
  (setq edata (entget ent)
        center (cdr (assoc 10 edata))
        radius (cdr (assoc 40 edata))
        startAng (cdr (assoc 50 edata))
        endAng (cdr (assoc 51 edata))
        elev (caddr center))
  (if (null elev) (setq elev 0.0))
  (if (< endAng startAng) (setq endAng (+ endAng (* 2.0 pi))))
  (setq seg 24 pts '() i 0)
  (while (<= i seg)
    (setq ang (+ startAng (* (/ (- endAng startAng) seg) i)))
    (setq pts (cons (list (+ (car center) (* radius (cos ang)))
                          (+ (cadr center) (* radius (sin ang)))
                          elev) pts))
    (setq i (1+ i))
  )
  (reverse pts)
)

;; تحويل الدائرة CIRCLE إلى مضلع نقاط مغلق
(defun Tessellate-Circle (ent / edata center radius elev seg pts ang i)
  (setq edata (entget ent)
        center (cdr (assoc 10 edata))
        radius (cdr (assoc 40 edata))
        elev (caddr center))
  (if (null elev) (setq elev 0.0))
  (setq seg 36 pts '() i 0)
  (while (<= i seg)
    (setq ang (* (/ (* 2.0 pi) seg) i))
    (setq pts (cons (list (+ (car center) (* radius (cos ang)))
                          (+ (cadr center) (* radius (sin ang)))
                          elev) pts))
    (setq i (1+ i))
  )
  (reverse pts)
)

;; حساب الأطوال ثنائية الأبعاد بطريقة آمنة
(defun Calc-Length (pts / len i p1 p2)
  (setq len 0.0 i 0)
  (if (and pts (listp pts) (> (length pts) 1))
    (while (< (1+ i) (length pts))
      (setq p1 (nth i pts) p2 (nth (1+ i) pts))
      (if (and p1 p2 (numberp (car p1)) (numberp (car p2)) (numberp (cadr p1)) (numberp (cadr p2)))
        (setq len (+ len (sqrt (+ (expt (- (car p2) (car p1)) 2) (expt (- (cadr p2) (cadr p1)) 2))))))
      (setq i (1+ i))
    )
  )
  len
)

;; حساب مساحة المضلع (Shoelace Formula) بطريقة آمنة
(defun Calc-Area (pts / area i n p1 p2)
  (setq area 0.0)
  (if (and pts (listp pts) (>= (length pts) 3))
    (progn
      (setq n (length pts) i 0)
      (while (< i (1- n))
        (setq p1 (nth i pts) p2 (nth (1+ i) pts))
        (if (and p1 p2 (numberp (car p1)) (numberp (car p2)) (numberp (cadr p1)) (numberp (cadr p2)))
          (setq area (+ area (- (* (car p1) (cadr p2)) (* (car p2) (cadr p1))))))
        (setq i (1+ i))
      )
      (setq area (abs (/ area 2.0)))
    )
  )
  area
)

;; استخراج العناصر الهندسية مع عزل الأخطاء
(defun Extract-CAD-Geometry (ss optClose / i n ent edata entType lyr isClosed pts elevG flag70 sub p1 p2 pt res lenVal areaVal)
  (setq res '() i 0 n (sslength ss))
  (while (< i n)
    (setq ent (ssname ss i)
          edata (entget ent)
          entType (cdr (assoc 0 edata))
          lyr (cdr (assoc 8 edata))
          isClosed nil
          pts '())
    (cond
      ((= entType "POINT")
       (setq pt (cdr (assoc 10 edata)))
       (if pt (setq pts (list (list (car pt) (cadr pt) (if (caddr pt) (caddr pt) 0.0))))))
      
      ((= entType "LINE")
       (setq p1 (cdr (assoc 10 edata)) p2 (cdr (assoc 11 edata)))
       (if (and p1 p2)
         (setq pts (list (list (car p1) (cadr p1) (if (caddr p1) (caddr p1) 0.0))
                         (list (car p2) (cadr p2) (if (caddr p2) (caddr p2) 0.0))))))
      
      ((= entType "ARC")
       (setq pts (Tessellate-Arc ent)))
      
      ((= entType "CIRCLE")
       (setq pts (Tessellate-Circle ent) isClosed T))
      
      ((= entType "LWPOLYLINE")
       (setq elevG (cdr (assoc 38 edata)))
       (if (null elevG) (setq elevG 0.0))
       (setq flag70 (cdr (assoc 70 edata)))
       (if (and flag70 (= (logand flag70 1) 1)) (setq isClosed T))
       (foreach item edata
         (if (= (car item) 10)
           (setq pts (cons (list (cadr item) (caddr item) elevG) pts))))
       (setq pts (reverse pts))
       (if (and (or isClosed (= optClose "1") (eq optClose T)) (> (length pts) 2))
         (setq pts (append pts (list (car pts))) isClosed T)))
      
      ((= entType "POLYLINE")
       (setq flag70 (cdr (assoc 70 edata)))
       (if (and flag70 (= (logand flag70 1) 1)) (setq isClosed T))
       (setq sub (entnext ent))
       (while (and sub (/= (cdr (assoc 0 (entget sub))) "SEQEND"))
         (if (= (cdr (assoc 0 (entget sub))) "VERTEX")
           (progn
             (setq pt (cdr (assoc 10 (entget sub))))
             (setq pts (cons (list (car pt) (cadr pt) (if (caddr pt) (caddr pt) 0.0)) pts))))
         (setq sub (entnext sub)))
       (setq pts (reverse pts))
       (if (and (or isClosed (= optClose "1") (eq optClose T)) (> (length pts) 2))
         (setq pts (append pts (list (car pts))) isClosed T)))
    )
    
    (if (and pts (> (length pts) 0))
      (progn
        (setq lenVal (Calc-Length pts))
        (setq areaVal (if isClosed (Calc-Area pts) 0.0))
        (setq res (cons (list (cons "type" entType)
                              (cons "layer" lyr)
                              (cons "closed" (if isClosed 1 0))
                              (cons "pts" pts)
                              (cons "length" (if (numberp lenVal) lenVal 0.0))
                              (cons "area" (if (numberp areaVal) areaVal 0.0))
                        ) res))
      )
    )
    (setq i (1+ i))
  )
  (reverse res)
)

;; بناء ملف KML
(defun Build-KML (data zone south dec / str item type lyr isCls pts pStr wgs col lenV areaV desc)
  (setq str (strcat "<?xml version=\"1.0\" encoding=\"UTF-8\"?>\n"
                    "<kml xmlns=\"http://www.opengis.net/kml/2.2\">\n"
                    "<Document>\n<name>AutoCAD Export - Zone " (rtos zone 2 0) (if south "S" "N") "</name>\n"))
  (foreach item data
    (setq type (cdr (assoc "type" item))
          lyr (cdr (assoc "layer" item))
          isCls (cdr (assoc "closed" item))
          pts (cdr (assoc "pts" item))
          lenV (cdr (assoc "length" item))
          areaV (cdr (assoc "area" item))
          col (Layer-Color-KML lyr))
    
    (if (not (numberp lenV)) (setq lenV 0.0))
    (if (not (numberp areaV)) (setq areaV 0.0))
    
    (setq desc (strcat "Layer: " (if lyr lyr "0")
                       (if (> lenV 0.0) (strcat " | Length: " (rtos lenV 2 2) " m") "")
                       (if (> areaV 0.0) (strcat " | Area: " (rtos areaV 2 2) " m2") "")))
    (setq str (strcat str "<Placemark>\n<name>" type " (" (if lyr lyr "0") ")</name>\n<description>" desc "</description>\n"
                      "<Style><LineStyle><color>" col "</color><width>3</width></LineStyle>"
                      "<PolyStyle><color>66" (substr col 3) "</color></PolyStyle></Style>\n"))
    (cond
      ((= type "POINT")
       (setq wgs (UTM->WGS84 (caar pts) (cadar pts) zone south))
       (setq str (strcat str "<Point><coordinates>" (rtos (car wgs) 2 7) "," (rtos (cadr wgs) 2 7) "," (rtos (if (caddar pts) (caddar pts) 0.0) 2 dec) "</coordinates></Point>\n")))
      
      ((= isCls 1)
       (setq pStr "")
       (foreach pt pts
         (setq wgs (UTM->WGS84 (car pt) (cadr pt) zone south))
         (setq pStr (strcat pStr (rtos (car wgs) 2 7) "," (rtos (cadr wgs) 2 7) "," (rtos (if (caddr pt) (caddr pt) 0.0) 2 dec) " ")))
       (setq str (strcat str "<Polygon><outerBoundaryIs><LinearRing><coordinates>" pStr "</coordinates></LinearRing></outerBoundaryIs></Polygon>\n")))
      
      (T
       (setq pStr "")
       (foreach pt pts
         (setq wgs (UTM->WGS84 (car pt) (cadr pt) zone south))
         (setq pStr (strcat pStr (rtos (car wgs) 2 7) "," (rtos (cadr wgs) 2 7) "," (rtos (if (caddr pt) (caddr pt) 0.0) 2 dec) " ")))
       (setq str (strcat str "<LineString><tessellate>1</tessellate><coordinates>" pStr "</coordinates></LineString>\n")))
    )
    (setq str (strcat str "</Placemark>\n"))
  )
  (strcat str "</Document>\n</kml>")
)

;; بناء ملف GeoJSON
(defun Build-GeoJSON (data zone south dec / str item type lyr isCls pts pStr wgs first geoType coordStr lenV areaV)
  (setq str "{\n  \"type\": \"FeatureCollection\",\n  \"features\": [\n")
  (setq first T)
  (foreach item data
    (setq type (cdr (assoc "type" item))
          lyr (cdr (assoc "layer" item))
          isCls (cdr (assoc "closed" item))
          pts (cdr (assoc "pts" item))
          lenV (cdr (assoc "length" item))
          areaV (cdr (assoc "area" item)))
    (if (not (numberp lenV)) (setq lenV 0.0))
    (if (not (numberp areaV)) (setq areaV 0.0))
    (if (not first) (setq str (strcat str ",\n")))
    (setq first nil)
    (cond
      ((= type "POINT")
       (setq wgs (UTM->WGS84 (caar pts) (cadar pts) zone south))
       (setq geoType "Point")
       (setq coordStr (strcat "[" (rtos (car wgs) 2 7) "," (rtos (cadr wgs) 2 7) "," (rtos (if (caddar pts) (caddar pts) 0.0) 2 dec) "]")))
      
      ((= isCls 1)
       (setq geoType "Polygon")
       (setq pStr "")
       (foreach pt pts
         (setq wgs (UTM->WGS84 (car pt) (cadr pt) zone south))
         (setq pStr (strcat pStr "[" (rtos (car wgs) 2 7) "," (rtos (cadr wgs) 2 7) "," (rtos (if (caddr pt) (caddr pt) 0.0) 2 dec) "],")))
       (if (= (substr pStr (strlen pStr)) ",") (setq pStr (substr pStr 1 (1- (strlen pStr)))))
       (setq coordStr (strcat "[[" pStr "]]")))
      
      (T
       (setq geoType "LineString")
       (setq pStr "")
       (foreach pt pts
         (setq wgs (UTM->WGS84 (car pt) (cadr pt) zone south))
         (setq pStr (strcat pStr "[" (rtos (car wgs) 2 7) "," (rtos (cadr wgs) 2 7) "," (rtos (if (caddr pt) (caddr pt) 0.0) 2 dec) "],")))
       (if (= (substr pStr (strlen pStr)) ",") (setq pStr (substr pStr 1 (1- (strlen pStr)))))
       (setq coordStr (strcat "[" pStr "]")))
    )
    (setq str (strcat str "    {\"type\": \"Feature\", \"properties\": {\"layer\": \"" (if lyr lyr "0") "\", \"entType\": \"" type
                          "\", \"length_m\": " (rtos lenV 2 2) ", \"area_m2\": " (rtos areaV 2 2)
                          "}, \"geometry\": {\"type\": \"" geoType "\", \"coordinates\": " coordStr "}}"))
  )
  (strcat str "\n  ]\n}")
)

;; كتابة تقرير HTML بنظام التدفق السطري (Stream Output لتفادي حدود النصوص الطويلة)
(defun Write-HTML-Report (filePath data utmZone south dec / stream f useStream item type lyr isCls pts ptStr lenV areaV)
  (setq useStream nil)
  (if (not (vl-catch-all-error-p
             (vl-catch-all-apply
               '(lambda ()
                  (setq stream (vlax-create-object "ADODB.Stream"))
                  (vlax-put-property stream 'Type 2)
                  (vlax-put-property stream 'Charset "utf-8")
                  (vlax-invoke-method stream 'Open)
                  (setq useStream T)
                ))))
    (setq useStream T)
  )
  (if (not useStream) (setq f (open filePath "w")))

  (defun WL (txt)
    (if useStream
      (vlax-invoke-method stream 'WriteText (strcat txt "\n"))
      (if f (write-line txt f))
    )
  )

  ;; 1. بنية الـ HTML والـ CSS
  (WL "<!DOCTYPE html>")
  (WL "<html lang=\"ar\" dir=\"rtl\">")
  (WL "<head>")
  (WL "<meta charset=\"UTF-8\">")
  (WL "<meta name=\"viewport\" content=\"width=device-width, initial-scale=1.0\">")
  (WL "<title>Technical Office - CAD GIS Report</title>")
  (WL "<link rel=\"stylesheet\" href=\"https://unpkg.com/leaflet@1.9.4/dist/leaflet.css\"/>")
  (WL "<script src=\"https://unpkg.com/leaflet@1.9.4/dist/leaflet.js\"></script>")
  (WL "<script src=\"https://cdnjs.cloudflare.com/ajax/libs/proj4js/2.9.0/proj4.js\"></script>")
  (WL "<script src=\"https://cdn.jsdelivr.net/npm/chart.js\"></script>")
  (WL "<style>")
  (WL "* { box-sizing: border-box; }")
  (WL "body { font-family: 'Segoe UI', Tahoma, Arial, sans-serif; margin: 0; padding: 15px; background: #f0f3f6; color: #1e293b; }")
  (WL ".card { background: #fff; border-radius: 8px; padding: 16px; margin-bottom: 15px; box-shadow: 0 2px 6px rgba(0,0,0,0.08); }")
  (WL ".header-bar { display: flex; justify-content: space-between; align-items: center; border-bottom: 2px solid #0078d4; padding-bottom: 12px; flex-wrap: wrap; gap: 10px; }")
  (WL ".header-title { font-size: 20px; font-weight: bold; color: #0078d4; margin: 0; }")
  (WL ".header-sub { color: #64748b; font-size: 13px; margin-top: 4px; }")
  (WL ".btn-group { display: flex; flex-wrap: wrap; gap: 8px; align-items: center; }")
  (WL ".btn { background: #008080; color: #fff; border: none; padding: 8px 16px; border-radius: 5px; cursor: pointer; font-weight: 600; font-size: 13px; display: inline-flex; align-items: center; gap: 6px; }")
  (WL ".btn:hover { background: #005f5f; }")
  (WL ".btn.alt { background: #0078d4; }")
  (WL ".btn.alt:hover { background: #005a9e; }")
  (WL ".btn.lang { background: #334155; color: #fff; font-weight: bold; }")
  (WL ".btn.lang:hover { background: #0f172a; }")
  (WL ".stats { display: flex; flex-wrap: wrap; gap: 12px; }")
  (WL ".stat-box { flex: 1; min-width: 130px; background: #f8fafc; border-radius: 6px; padding: 12px; text-align: center; border: 1px solid #e2e8f0; }")
  (WL ".stat-box b { display: block; font-size: 22px; color: #0078d4; margin-bottom: 4px; }")
  (WL ".stat-box span { font-size: 12px; color: #64748b; font-weight: 600; }")
  (WL "#xyPlot { max-height: 280px; width: 100%; background: #0b1726; border-radius: 6px; }")
  (WL "#map { height: 530px; width: 100%; border-radius: 6px; border: 1px solid #cbd5e1; }")
  (WL ".table-header { display: flex; justify-content: space-between; align-items: center; margin-bottom: 10px; flex-wrap: wrap; gap: 8px; }")
  (WL "input#searchBox { padding: 8px 12px; border-radius: 5px; border: 1px solid #cbd5e1; width: 250px; font-size: 13px; }")
  (WL "table { width: 100%; border-collapse: collapse; margin-top: 6px; font-size: 13px; }")
  (WL "th, td { border: 1px solid #e2e8f0; padding: 8px 10px; text-align: center; }")
  (WL "th { background: #0078d4; color: #fff; font-weight: 600; }")
  (WL "tr:nth-child(even) { background: #f8fafc; }")
  (WL "tr:hover { background: #f1f5f9; }")
  (WL ".swatch { display: inline-block; width: 12px; height: 12px; border-radius: 3px; margin: 0 4px; vertical-align: middle; }")
  (WL "</style>")
  (WL "</head>")
  (WL "<body>")

  ;; 2. واجهة التقرير
  (WL "<div class=\"card\">")
  (WL "  <div class=\"header-bar\">")
  (WL "    <div>")
  (WL "      <h1 class=\"header-title\" id=\"lbl-title\"></h1>")
  (WL "      <div class=\"header-sub\" id=\"lbl-proj\"></div>")
  (WL "    </div>")
  (WL "    <div class=\"btn-group\">")
  (WL "      <button class=\"btn lang\" id=\"btn-lang\" onclick=\"toggleLanguage()\"></button>")
  (WL "      <button class=\"btn\" id=\"btn-kml\" onclick=\"downloadKML()\"></button>")
  (WL "      <button class=\"btn alt\" id=\"btn-csv\" onclick=\"downloadCSV()\"></button>")
  (WL "      <button class=\"btn alt\" id=\"btn-geo\" onclick=\"downloadGeoJSON()\"></button>")
  (WL "    </div>")
  (WL "  </div>")
  (WL "</div>")

  (WL "<div class=\"card\">")
  (WL "  <div class=\"stats\">")
  (WL "    <div class=\"stat-box\"><b id=\"stat-total\">0</b><span id=\"lbl-total\"></span></div>")
  (WL "    <div class=\"stat-box\"><b id=\"stat-pts\">0</b><span id=\"lbl-pts\"></span></div>")
  (WL "    <div class=\"stat-box\"><b id=\"stat-lines\">0</b><span id=\"lbl-lines\"></span></div>")
  (WL "    <div class=\"stat-box\"><b id=\"stat-polys\">0</b><span id=\"lbl-polys\"></span></div>")
  (WL "    <div class=\"stat-box\"><b id=\"stat-len\">0.00</b><span id=\"lbl-len\"></span></div>")
  (WL "    <div class=\"stat-box\"><b id=\"stat-area\">0.00</b><span id=\"lbl-area\"></span></div>")
  (WL "  </div>")
  (WL "</div>")

  (WL "<div class=\"card\">")
  (WL "  <h3 id=\"lbl-xy-title\" style=\"margin-top:0;\"></h3>")
  (WL "  <canvas id=\"xyPlot\"></canvas>")
  (WL "</div>")

  (WL "<div class=\"card\">")
  (WL "  <h3 id=\"lbl-map-title\" style=\"margin-top:0;\"></h3>")
  (WL "  <div id=\"map\"></div>")
  (WL "</div>")

  (WL "<div class=\"card\">")
  (WL "  <div class=\"table-header\">")
  (WL "    <h3 id=\"lbl-table-title\" style=\"margin:0;\"></h3>")
  (WL "    <input id=\"searchBox\" onkeyup=\"filterTable()\">")
  (WL "  </div>")
  (WL "  <table id=\"dataTable\">")
  (WL "    <thead>")
  (WL "      <tr>")
  (WL "        <th id=\"th-num\">#</th>")
  (WL "        <th id=\"th-type\"></th>")
  (WL "        <th id=\"th-layer\"></th>")
  (WL "        <th id=\"th-east\"></th>")
  (WL "        <th id=\"th-north\"></th>")
  (WL "        <th id=\"th-elev\"></th>")
  (WL "      </tr>")
  (WL "    </thead>")
  (WL "    <tbody></tbody>")
  (WL "  </table>")
  (WL "</div>")

  ;; 3. حقن مصفوفة البيانات ومحرك الجافاسكربت
  (WL "<script>")
  (WL "const data = [")
  (foreach item data
    (setq type (cdr (assoc "type" item))
          lyr (cdr (assoc "layer" item))
          isCls (cdr (assoc "closed" item))
          pts (cdr (assoc "pts" item))
          lenV (cdr (assoc "length" item))
          areaV (cdr (assoc "area" item)))
    (if (not (numberp lenV)) (setq lenV 0.0))
    (if (not (numberp areaV)) (setq areaV 0.0))
    (setq ptStr "[")
    (foreach p pts
      (setq ptStr (strcat ptStr "[" (rtos (car p) 2 dec) "," (rtos (cadr p) 2 dec) "," (rtos (if (caddr p) (caddr p) 0.0) 2 dec) "],")))
    (if (= (substr ptStr (strlen ptStr)) ",") (setq ptStr (substr ptStr 1 (1- (strlen ptStr)))))
    (setq ptStr (strcat ptStr "]"))
    (WL (strcat "  {\"type\":\"" type "\",\"layer\":\"" (if lyr lyr "0") "\",\"closed\":" (itoa isCls)
                ",\"len\":" (rtos lenV 2 2) ",\"area\":" (rtos areaV 2 2) ",\"pts\":" ptStr "},"))
  )
  (WL "];")

  (WL (strcat "const utmZone = " utmZone ";"))
  (WL (strcat "const isSouth = " (if south "true" "false") ";"))
  (WL (strcat "const decPlaces = " (itoa dec) ";"))
  (WL "const utmDef = `+proj=utm +zone=${utmZone} ${isSouth ? '+south ' : ''}+datum=WGS84 +units=m +no_defs`;")

  ;; القاموس ثنائي اللغة بتشفير الـ Unicode المباشر
  (WL "const i18n = {")
  (WL "  ar: {")
  (WL "    title: \"\\u0627\\u0644\\u0645\\u0643\\u062a\\u0628 \\u0627\\u0644\\u0641\\u0646\\u064a - \\u062a\\u0642\\u0631\\u064a\\u0631 \\u0645\\u0637\\u0627\\u0628\\u0642\\u0629 \\u0627\\u0644\\u0645\\u062e\\u0637\\u0637\\u0627\\u062a \\u0648\\u0627\\u0644\\u0631\\u0641\\u0639 \\u0627\\u0644\\u0645\\u0633\\u0627\\u062d\\u064a\",")
  (WL (strcat "    proj: \"\\u0646\\u0638\\u0627\\u0645 \\u0627\\u0644\\u0625\\u0633\\u0642\\u0627\\u0637: UTM Zone " utmZone (if south "S" "N") " (WGS84)\","))
  (WL "    kmlBtn: \"\\u2193 \\u062a\\u062d\\u0645\\u064a\\u0644 KML\",")
  (WL "    csvBtn: \"\\u2193 \\u062a\\u062d\\u0645\\u064a\\u0644 CSV\",")
  (WL "    geoBtn: \"\\u2193 \\u062a\\u062d\\u0645\\u064a\\u0644 GeoJSON\",")
  (WL "    langBtn: \"English\",")
  (WL "    totalEnt: \"\\u0625\\u062c\\u0645\\u0627\\u0644\\u064a \\u0627\\u0644\\u0639\\u0646\\u0627\\u0635\\u0631\",")
  (WL "    ptsCount: \"\\u0646\\u0642\\u0627\\u0637\",")
  (WL "    linesCount: \"\\u062e\\u0637\\u0648\\u0637 / \\u0628\\u0648\\u0644\\u064a \\u0644\\u0627\\u064a\\u0646\",")
  (WL "    polysCount: \"\\u0645\\u0636\\u0644\\u0639\\u0627\\u062a \\u0645\\u063a\\u0644\\u0642\\u0629\",")
  (WL "    totalLen: \"\\u0625\\u062c\\u0645\\u0627\\u0644\\u064a \\u0627\\u0644\\u0623\\u0637\\u0648\\u0627\\u0644 (\\u0645)\",")
  (WL "    totalArea: \"\\u0625\\u062c\\u0645\\u0627\\u0644\\u064a \\u0627\\u0644\\u0645\\u0633\\u0627\\u062d\\u0627\\u062a (\\u0645\\u00b2)\",")
  (WL "    xyTitle: \"\\u0645\\u0639\\u0627\\u064a\\u0646\\u0629 \\u0645\\u0648\\u0627\\u0642\\u0639 \\u0627\\u0644\\u0646\\u0642\\u0627\\u0637 \\u0648\\u0627\\u0644\\u0639\\u0646\\u0627\\u0635\\u0631 (\\u0645\\u062e\\u0637\\u0637 XY)\",")
  (WL "    mapTitle: \"\\u0627\\u0644\\u062e\\u0631\\u064a\\u0637\\u0629 \\u0627\\u0644\\u062c\\u063a\\u0631\\u0627\\u0641\\u064a\\u0629 \\u0627\\u0644\\u062a\\u0641\\u0627\\u0639\\u0644\\u064a\\u0629 \\u0648\\u0645\\u0637\\u0627\\u0628\\u0642\\u0629 \\u0627\\u0644\\u0623\\u0642\\u0645\\u0627\\u0631 \\u0627\\u0644\\u0635\\u0646\\u0627\\u0639\\u064a\\u0629\",")
  (WL "    tableTitle: \"\\u062c\\u062f\\u0648\\u0644 \\u062d\\u0635\\u0631 \\u0627\\u0644\\u0625\\u062d\\u062f\\u0627\\u062b\\u064a\\u0627\\u062a \\u0648\\u0627\\u0644\\u0639\\u0646\\u0627\\u0635\\u0631 \\u0627\\u0644\\u0645\\u0643\\u062a\\u0634\\u0641\\u0629\",")
  (WL "    searchPh: \"\\u0628\\u062d\\u062b \\u0641\\u064a \\u0627\\u0644\\u0637\\u0628\\u0642\\u0629 \\u0623\\u0648 \\u0627\\u0644\\u0646\\u0648\\u0639...\",")
  (WL "    thNum: \"#\",")
  (WL "    thType: \"\\u0627\\u0644\\u0646\\u0648\\u0639\",")
  (WL "    thLayer: \"\\u0627\\u0644\\u0637\\u0628\\u0642\\u0629 (Layer)\",")
  (WL "    thEast: \"Easting (X)\",")
  (WL "    thNorth: \"Northing (Y)\",")
  (WL "    thElev: \"Elevation (Z)\",")
  (WL "    ptLabel: \"\\u0646\\u0642\\u0637\\u0629 \\u0645\\u0633\\u0627\\u062d\\u064a\\u0629\",")
  (WL "    polyLabel: \"\\u0645\\u0636\\u0644\\u0639 \\u0645\\u063a\\u0644\\u0642\",")
  (WL "    lineLabel: \"\\u062e\\u0637 / \\u0628\\u0648\\u0644\\u064a \\u0644\\u0627\\u064a\\u0646\",")
  (WL "    lenLabel: \"\\u0627\\u0644\\u0637\\u0648\\u0644\",")
  (WL "    areaLabel: \"\\u0627\\u0644\\u0645\\u0633\\u0627\\u062d\\u0629\",")
  (WL "    layerLabel: \"\\u0627\\u0644\\u0637\\u0628\\u0642\\u0629\",")
  (WL "    mUnit: \"\\u0645\",")
  (WL "    sqmUnit: \"\\u0645\\u00b2\"")
  (WL "  },")
  (WL "  en: {")
  (WL "    title: \"Technical Office - CAD Survey & GIS Mapping Report\",")
  (WL (strcat "    proj: \"Projection: UTM Zone " utmZone (if south "S" "N") " (WGS84)\","))
  (WL "    kmlBtn: \"\\u2193 Download KML\",")
  (WL "    csvBtn: \"\\u2193 Download CSV\",")
  (WL "    geoBtn: \"\\u2193 Download GeoJSON\",")
  (WL "    langBtn: \"\\u0639\\u0631\\u0628\\u064a\",")
  (WL "    totalEnt: \"Total Entities\",")
  (WL "    ptsCount: \"Points\",")
  (WL "    linesCount: \"Lines / Polylines\",")
  (WL "    polysCount: \"Closed Polygons\",")
  (WL "    totalLen: \"Total Length (m)\",")
  (WL "    totalArea: \"Total Area (m\\u00b2)\",")
  (WL "    xyTitle: \"Entity & Point Location Preview (XY Plot)\",")
  (WL "    mapTitle: \"Interactive Web GIS & Satellite Verification\",")
  (WL "    tableTitle: \"Extracted Coordinates & Survey Inventory Table\",")
  (WL "    searchPh: \"Search by layer or type...\",")
  (WL "    thNum: \"#\",")
  (WL "    thType: \"Type\",")
  (WL "    thLayer: \"Layer\",")
  (WL "    thEast: \"Easting (X)\",")
  (WL "    thNorth: \"Northing (Y)\",")
  (WL "    thElev: \"Elevation (Z)\",")
  (WL "    ptLabel: \"Survey Point\",")
  (WL "    polyLabel: \"Closed Polygon\",")
  (WL "    lineLabel: \"Line / Polyline\",")
  (WL "    lenLabel: \"Length\",")
  (WL "    areaLabel: \"Area\",")
  (WL "    layerLabel: \"Layer\",")
  (WL "    mUnit: \"m\",")
  (WL "    sqmUnit: \"m\\u00b2\"")
  (WL "  }")
  (WL "};")

  (WL "let curLang = 'ar';")

  (WL "function hashColor(str){")
  (WL "  let h=0; for(let i=0; i<str.length; i++){ h = str.charCodeAt(i) + ((h<<5)-h); }")
  (WL "  const c = (h & 0x00FFFFFF).toString(16).padStart(6,'0'); return '#' + c;")
  (WL "}")

  (WL "function updateUI() {")
  (WL "  const t = i18n[curLang];")
  (WL "  document.documentElement.lang = curLang;")
  (WL "  document.documentElement.dir = (curLang === 'ar') ? 'rtl' : 'ltr';")
  (WL "  document.getElementById('lbl-title').textContent = t.title;")
  (WL "  document.getElementById('lbl-proj').textContent = t.proj;")
  (WL "  document.getElementById('btn-kml').textContent = t.kmlBtn;")
  (WL "  document.getElementById('btn-csv').textContent = t.csvBtn;")
  (WL "  document.getElementById('btn-geo').textContent = t.geoBtn;")
  (WL "  document.getElementById('btn-lang').textContent = t.langBtn;")
  (WL "  document.getElementById('lbl-total').textContent = t.totalEnt;")
  (WL "  document.getElementById('lbl-pts').textContent = t.ptsCount;")
  (WL "  document.getElementById('lbl-lines').textContent = t.linesCount;")
  (WL "  document.getElementById('lbl-polys').textContent = t.polysCount;")
  (WL "  document.getElementById('lbl-len').textContent = t.totalLen;")
  (WL "  document.getElementById('lbl-area').textContent = t.totalArea;")
  (WL "  document.getElementById('lbl-xy-title').textContent = t.xyTitle;")
  (WL "  document.getElementById('lbl-map-title').textContent = t.mapTitle;")
  (WL "  document.getElementById('lbl-table-title').textContent = t.tableTitle;")
  (WL "  document.getElementById('searchBox').placeholder = t.searchPh;")
  (WL "  document.getElementById('th-num').textContent = t.thNum;")
  (WL "  document.getElementById('th-type').textContent = t.thType;")
  (WL "  document.getElementById('th-layer').textContent = t.thLayer;")
  (WL "  document.getElementById('th-east').textContent = t.thEast;")
  (WL "  document.getElementById('th-north').textContent = t.thNorth;")
  (WL "  document.getElementById('th-elev').textContent = t.thElev;")
  (WL "  renderMapAndPopups();")
  (WL "}")

  (WL "function toggleLanguage() { curLang = (curLang === 'ar') ? 'en' : 'ar'; updateUI(); }")

  (WL "let ptCount = 0, lineCount = 0, polyCount = 0, totalLen = 0.0, totalArea = 0.0;")
  (WL "data.forEach(item => {")
  (WL "  totalLen += (item.len || 0.0); totalArea += (item.area || 0.0);")
  (WL "  if(item.type === 'POINT') ptCount++; else if(item.closed === 1) polyCount++; else lineCount++;")
  (WL "});")
  (WL "document.getElementById('stat-total').textContent = data.length;")
  (WL "document.getElementById('stat-pts').textContent = ptCount;")
  (WL "document.getElementById('stat-lines').textContent = lineCount;")
  (WL "document.getElementById('stat-polys').textContent = polyCount;")
  (WL "document.getElementById('stat-len').textContent = totalLen.toFixed(2);")
  (WL "document.getElementById('stat-area').textContent = totalArea.toFixed(2);")

  (WL "let rows = '', idx = 1;")
  (WL "data.forEach(item => {")
  (WL "  const col = hashColor(item.layer || '0');")
  (WL "  item.pts.forEach(p => {")
  (WL "    rows += `<tr data-layer=\"${(item.layer||'').toLowerCase()}\" data-type=\"${(item.type||'').toLowerCase()}\">")
  (WL "      <td>${idx++}</td><td>${item.type}</td><td><span class=\"swatch\" style=\"background:${col}\"></span>${item.layer}</td>")
  (WL "      <td>${Number(p[0]).toFixed(decPlaces)}</td><td>${Number(p[1]).toFixed(decPlaces)}</td><td>${Number(p[2]||0).toFixed(decPlaces)}</td></tr>`;")
  (WL "  });")
  (WL "});")
  (WL "document.querySelector('#dataTable tbody').innerHTML = rows;")

  (WL "let xySets = [];")
  (WL "data.forEach(item => {")
  (WL "  const col = hashColor(item.layer || '0');")
  (WL "  xySets.push({ label: item.layer, data: item.pts.map(p => ({ x: p[0], y: p[1] })), borderColor: col, backgroundColor: col, showLine: item.type !== 'POINT' });")
  (WL "});")
  (WL "new Chart(document.getElementById('xyPlot'), {")
  (WL "  type: 'scatter', data: { datasets: xySets },")
  (WL "  options: { responsive: true, scales: { x: { grid: { color: '#1e293b' } }, y: { grid: { color: '#1e293b' } } }, plugins: { legend: { labels: { color: '#cbd5e1' } } } }")
  (WL "});")

  (WL "const gHyb = L.tileLayer('https://mt1.google.com/vt/lyrs=y&x={x}&y={y}&z={z}', { maxZoom: 22, attribution: 'Google Hybrid' });")
  (WL "const gSat = L.tileLayer('https://mt1.google.com/vt/lyrs=s&x={x}&y={y}&z={z}', { maxZoom: 22, attribution: 'Google Sat' });")
  (WL "const gStr = L.tileLayer('https://mt1.google.com/vt/lyrs=m&x={x}&y={y}&z={z}', { maxZoom: 22, attribution: 'Google Streets' });")
  (WL "const esri = L.tileLayer('https://server.arcgisonline.com/ArcGIS/rest/services/World_Imagery/MapServer/tile/{z}/{y}/{x}', { attribution: 'Esri Sat' });")
  (WL "const osm  = L.tileLayer('https://{s}.tile.openstreetmap.org/{z}/{x}/{y}.png', { attribution: 'OSM' });")
  (WL "const map = L.map('map', { center: [26, 44], zoom: 6, layers: [gHyb] });")
  (WL "L.control.layers({ 'Google Hybrid': gHyb, 'Google Sat': gSat, 'Google Streets': gStr, 'Esri Sat': esri, 'OSM': osm }).addTo(map);")
  (WL "let mapLayersGroup = L.layerGroup().addTo(map);")

  (WL "function renderMapAndPopups() {")
  (WL "  mapLayersGroup.clearLayers(); const t = i18n[curLang]; let mapBounds = [];")
  (WL "  data.forEach(item => {")
  (WL "    const col = hashColor(item.layer || '0');")
  (WL "    let latLngs = item.pts.map(p => { let w = proj4(utmDef, 'WGS84', [p[0], p[1]]); return [w[1], w[0]]; });")
  (WL "    mapBounds.push(...latLngs);")
  (WL "    let labelType = (item.type === 'POINT') ? t.ptLabel : (item.closed === 1 ? t.polyLabel : t.lineLabel);")
  (WL "    let popupInfo = `<b>${labelType}</b><br>${t.layerLabel}: ${item.layer}` + (item.len > 0 ? `<br>${t.lenLabel}: ${item.len.toFixed(2)} ${t.mUnit}` : '') + (item.area > 0 ? `<br>${t.areaLabel}: ${item.area.toFixed(2)} ${t.sqmUnit}` : '');")
  (WL "    if(item.type === 'POINT') latLngs.forEach(ll => L.circleMarker(ll, { radius: 6, color: col, fillColor: '#fff', fillOpacity: 0.9, weight: 2 }).addTo(mapLayersGroup).bindPopup(popupInfo));")
  (WL "    else if(item.closed === 1) L.polygon(latLngs, { color: col, fillColor: col, fillOpacity: 0.25, weight: 3 }).addTo(mapLayersGroup).bindPopup(popupInfo);")
  (WL "    else L.polyline(latLngs, { color: col, weight: 3 }).addTo(mapLayersGroup).bindPopup(popupInfo);")
  (WL "  });")
  (WL "  if (mapBounds.length) map.fitBounds(mapBounds, { padding: [30, 30] });")
  (WL "}")

  (WL "function filterTable(){")
  (WL "  const q = document.getElementById('searchBox').value.toLowerCase();")
  (WL "  document.querySelectorAll('#dataTable tbody tr').forEach(tr => {")
  (WL "    const match = tr.dataset.layer.includes(q) || tr.dataset.type.includes(q);")
  (WL "    tr.style.display = match ? '' : 'none';")
  (WL "  });")
  (WL "}")

  (WL "function downloadKML() {")
  (WL "  let kml = `<?xml version=\"1.0\" encoding=\"UTF-8\"?>\\n<kml xmlns=\"http://www.opengis.net/kml/2.2\">\\n<Document>\\n<name>Exported CAD Plan</name>\\n`;")
  (WL "  data.forEach(item => {")
  (WL "    kml += `<Placemark>\\n<name>${item.type} - ${item.layer}</name>\\n`;")
  (WL "    if(item.type === 'POINT'){ let w = proj4(utmDef, 'WGS84', [item.pts[0][0], item.pts[0][1]]); kml += `<Point><coordinates>${w[0]},${w[1]},${item.pts[0][2]||0}</coordinates></Point>\\n`; }")
  (WL "    else if(item.closed === 1){ let coords = item.pts.map(p => { let w = proj4(utmDef, 'WGS84', [p[0], p[1]]); return `${w[0]},${w[1]},${p[2]||0}`; }).join(' '); kml += `<Polygon><outerBoundaryIs><LinearRing><coordinates>${coords}</coordinates></LinearRing></outerBoundaryIs></Polygon>\\n`; }")
  (WL "    else { let coords = item.pts.map(p => { let w = proj4(utmDef, 'WGS84', [p[0], p[1]]); return `${w[0]},${w[1]},${p[2]||0}`; }).join(' '); kml += `<LineString><tessellate>1</tessellate><coordinates>${coords}</coordinates></LineString>\\n`; }")
  (WL "    kml += `</Placemark>\\n`;")
  (WL "  });")
  (WL "  kml += `</Document>\\n</kml>`;")
  (WL "  triggerDownload(kml, 'AutoCAD_Plan.kml', 'application/vnd.google-earth.kml+xml');")
  (WL "}")

  (WL "function downloadCSV(){")
  (WL "  let csv = 'Type,Layer,X,Y,Z\\n';")
  (WL "  data.forEach(item => { item.pts.forEach(p => { csv += `\"${item.type}\",\"${item.layer}\",${p[0]},${p[1]},${p[2]||0}\\n`; }); });")
  (WL "  triggerDownload(csv, 'AutoCAD_Coordinates.csv', 'text/csv;charset=utf-8;');")
  (WL "}")

  (WL "function downloadGeoJSON(){")
  (WL "  const features = data.map(item => {")
  (WL "    let geom; const coordsWGS = item.pts.map(p => { let w = proj4(utmDef, 'WGS84', [p[0], p[1]]); return [w[0], w[1], p[2]||0]; });")
  (WL "    if(item.type === 'POINT') geom = { type: 'Point', coordinates: coordsWGS[0] };")
  (WL "    else if(item.closed === 1) geom = { type: 'Polygon', coordinates: [coordsWGS] };")
  (WL "    else geom = { type: 'LineString', coordinates: coordsWGS };")
  (WL "    return { type: 'Feature', properties: { layer: item.layer, entType: item.type, length_m: item.len, area_m2: item.area }, geometry: geom };")
  (WL "  });")
  (WL "  const fc = { type: 'FeatureCollection', features: features };")
  (WL "  triggerDownload(JSON.stringify(fc, null, 2), 'AutoCAD_Export.geojson', 'application/geo+json');")
  (WL "}")

  (WL "function triggerDownload(content, filename, mime){")
  (WL "  let blob = new Blob([content], { type: mime });")
  (WL "  let a = document.createElement('a'); a.href = URL.createObjectURL(blob); a.download = filename; a.click();")
  (WL "}")

  (WL "updateUI();")
  (WL "</script>")
  (WL "</body>")
  (WL "</html>")

  (if useStream
    (progn
      (vlax-invoke-method stream 'SaveToFile filePath 2)
      (vlax-invoke-method stream 'Close)
      (vlax-release-object stream)
    )
    (if f (close f))
  )
  T
)

;; الدالة التنفيذية للواجهة والعمليات
(defun Main-CAD2EARTH ( / *error* dclFile f dclID dclStatus ss utmZone decPlaces optClose optHTML optKML optSouth optGeoJSON saveDir baseName entData kmlPath htmlPath geoPath zoneIdx decIdx countStr southFlag isSaved)
  
  (defun *error* (msg)
    (if (and dclID (> dclID 0)) (unload_dialog dclID))
    (if (and dclFile (findfile dclFile)) (vl-file-delete dclFile))
    (if (and msg (not (wcmatch (strcase msg t) "*cancel*,*exit*,*quit*")))
      (princ (strcat "\n[!] حدث خطأ: " msg))
    )
    (princ)
  )

  (setq utmZone "38"
        zoneIdx "2"
        decPlaces 3
        decIdx "1"
        optClose "1"
        optKML "1"
        optHTML "1"
        optSouth "0"
        optGeoJSON "0"
        ss nil
        countStr "العناصر: لم يتم التحديد")

  (setq dclFile (vl-filename-mktemp "cad2earth.dcl"))
  (setq f (open dclFile "w"))
  (write-line "cad2earth_dlg : dialog { label = \"المكتب الفني - تصدير الخرائط و KML\";" f)
  (write-line "  : boxed_column { label = \"تحديد العناصر من الرسم\";" f)
  (write-line "    : row {" f)
  (write-line "      : button { key = \"btn_select\"; label = \"حدّد العناصر...\"; width = 18; }" f)
  (write-line "      : text { key = \"lbl_count\"; label = \"العناصر: 0\"; width = 22; alignment = centered; }" f)
  (write-line "    }" f)
  (write-line "  }" f)
  (write-line "  : boxed_column { label = \"الإعدادات الهندسية\";" f)
  (write-line "    : row {" f)
  (write-line "      : popup_list { key = \"pop_zone\"; label = \"نطاق UTM:\"; width = 14; }" f)
  (write-line "      : popup_list { key = \"pop_dec\"; label = \"المنازل:\"; width = 8; }" f)
  (write-line "    }" f)
  (write-line "    : toggle { key = \"chk_south\"; label = \"نصف الكرة الجنوبي (جنوب خط الاستواء)\"; value = \"0\"; }" f)
  (write-line "    : toggle { key = \"chk_close\"; label = \"إغلاق البولي لاين ومطابقة المضلعات\"; value = \"1\"; }" f)
  (write-line "  }" f)
  (write-line "  : boxed_column { label = \"خيارات التصدير والمخرجات\";" f)
  (write-line "    : toggle { key = \"chk_kml\"; label = \"حفظ ملف KML مباشر (Google Earth)\"; value = \"1\"; }" f)
  (write-line "    : toggle { key = \"chk_html\"; label = \"توليد تقرير HTML تفاعلي مع الخرائط\"; value = \"1\"; }" f)
  (write-line "    : toggle { key = \"chk_geojson\"; label = \"حفظ ملف GeoJSON مستقل\"; value = \"0\"; }" f)
  (write-line "  }" f)
  (write-line "  : spacer { height = 1; }" f)
  (write-line "  ok_cancel;" f)
  (write-line "}" f)
  (close f)

  (setq dclID (load_dialog dclFile))
  (setq dclStatus 2)

  (while (= dclStatus 2)
    (if (new_dialog "cad2earth_dlg" dclID)
      (progn
        (start_list "pop_zone")
        (add_list "36N")
        (add_list "37N")
        (add_list "38N (القصيم/الرياض)")
        (add_list "39N (الشرقية)")
        (add_list "40N")
        (end_list)
        (set_tile "pop_zone" zoneIdx)

        (start_list "pop_dec")
        (add_list "2")
        (add_list "3")
        (add_list "4")
        (end_list)
        (set_tile "pop_dec" decIdx)

        (set_tile "chk_close" optClose)
        (set_tile "chk_kml" optKML)
        (set_tile "chk_html" optHTML)
        (set_tile "chk_south" optSouth)
        (set_tile "chk_geojson" optGeoJSON)
        (set_tile "lbl_count" countStr)

        (action_tile "btn_select"
          "(setq zoneIdx (get_tile \"pop_zone\")
                 decIdx (get_tile \"pop_dec\")
                 optClose (get_tile \"chk_close\")
                 optKML (get_tile \"chk_kml\")
                 optHTML (get_tile \"chk_html\")
                 optSouth (get_tile \"chk_south\")
                 optGeoJSON (get_tile \"chk_geojson\"))
           (done_dialog 2)"
        )

        (action_tile "accept"
          "(setq zoneIdx (get_tile \"pop_zone\")
                 decIdx (get_tile \"pop_dec\")
                 optClose (get_tile \"chk_close\")
                 optKML (get_tile \"chk_kml\")
                 optHTML (get_tile \"chk_html\")
                 optSouth (get_tile \"chk_south\")
                 optGeoJSON (get_tile \"chk_geojson\")
                 utmZone (nth (atoi (get_tile \"pop_zone\")) '(\"36\" \"37\" \"38\" \"39\" \"40\"))
                 decPlaces (atoi (nth (atoi (get_tile \"pop_dec\")) '(\"2\" \"3\" \"4\"))))
           (done_dialog 1)"
        )

        (action_tile "cancel" "(done_dialog 0)")

        (setq dclStatus (start_dialog))

        (if (= dclStatus 2)
          (progn
            (princ "\n>>> حدد العناصر (Points, Lines, Arcs, Circles, Polylines) ثم اضغط Enter: ")
            (setq ss (ssget '((0 . "POINT,LINE,LWPOLYLINE,POLYLINE,ARC,CIRCLE"))))
            (if (and ss (> (sslength ss) 0))
              (setq countStr (strcat "تم تحديد: " (itoa (sslength ss))))
              (setq countStr "لم يتم اختيار عناصر")
            )
          )
        )
      )
      (setq dclStatus 0)
    )
  )

  (unload_dialog dclID)
  (setq dclID nil)
  (vl-file-delete dclFile)

  ;; المعالجة والتصدير
  (if (and (= dclStatus 1) ss (> (sslength ss) 0))
    (progn
      (setq southFlag (= optSouth "1"))
      (setq isSaved (= (getvar "DWGTITLED") 1))
      (setq saveDir (getvar "DWGPREFIX"))
      (setq baseName (vl-filename-base (getvar "DWGNAME")))

      ;; فحص سلامة المسار وتأمينه
      (if (or (not isSaved) (null saveDir) (= saveDir "") (not (Is-Writable-Dir saveDir)))
        (progn
          (setq saveDir (getvar "TEMPPREFIX"))
          (if (or (null baseName) (= baseName "")) (setq baseName "CAD_Survey_Plan"))
          (princ (strcat "\n[!] تم ضبط مسار الحفظ المتاح:\n    " saveDir))
        )
      )

      (princ "\n>>> جاري استخراج ومعالجة بيانات العناصر...")
      (setq entData (Extract-CAD-Geometry ss optClose))

      (if (or (null entData) (= (length entData) 0))
        (princ "\n[!] تنبيه: لم يتم استخراج أي إحداثيات صالحة من العناصر المحددة.")
        (progn
          ;; 1. حفظ KML
          (if (= optKML "1")
            (progn
              (setq kmlPath (strcat saveDir baseName "_" utmZone (if southFlag "S" "N") ".kml"))
              (if (Write-UTF8 kmlPath (Build-KML entData (atof utmZone) southFlag decPlaces))
                (princ (strcat "\n[✓] تم حفظ ملف KML بنجاح: " kmlPath))
                (princ (strcat "\n[!] تعذر حفظ ملف KML في: " kmlPath))
              )
            )
          )

          ;; 2. حفظ GeoJSON
          (if (= optGeoJSON "1")
            (progn
              (setq geoPath (strcat saveDir baseName "_" utmZone (if southFlag "S" "N") ".geojson"))
              (if (Write-UTF8 geoPath (Build-GeoJSON entData (atof utmZone) southFlag decPlaces))
                (princ (strcat "\n[✓] تم حفظ ملف GeoJSON بنجاح: " geoPath))
                (princ (strcat "\n[!] تعذر حفظ ملف GeoJSON في: " geoPath))
              )
            )
          )

          ;; 3. حفظ HTML وفتحه
          (if (= optHTML "1")
            (progn
              (setq htmlPath (strcat saveDir baseName "_Report.html"))
              (if (Write-HTML-Report htmlPath entData utmZone southFlag decPlaces)
                (progn
                  (princ (strcat "\n[✓] تم حفظ تقرير HTML بنجاح: " htmlPath))
                  (vl-catch-all-apply 'vl-cmdf (list "_.browser" htmlPath))
                )
                (princ (strcat "\n[!] تعذر حفظ تقرير HTML في: " htmlPath))
              )
            )
          )
        )
      )
    )
    (if (= dclStatus 1)
      (princ "\n[!] تنبيه: لم يتم تحديد أي عناصر للتصدير.")
      (princ "\n[!] تم إلغاء العملية.")
    )
  )
  (princ)
)

;; اختصارات التشغيل
(defun c:CE () (Main-CAD2EARTH))
(defun c:CADEARTH () (Main-CAD2EARTH))
(defun c:CAD2MAP () (Main-CAD2EARTH))
(defun c:CAD2EARTH () (Main-CAD2EARTH))

(princ "\n[✓] تم تحميل CADEARTH PRO بنجاح! الاختصارات: CE أو CADEARTH")
(princ)
